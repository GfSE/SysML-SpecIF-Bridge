# Case-Study SmAV with SysML
System Specification of a Small Autonomous Vehicle built with Lego Mindstorm EV3 Kit.
- Rights: Creative Commons 4.0 CC BY-SA, https://creativecommons.org/licenses/by-sa/4.0/

## Requirements (SpecIF:Heading)

## Functions (SpecIF:Heading)

## Logical Solution (SpecIF:Heading)

## Physical Solution (SpecIF:Heading)

## Original Requirement Specification (SpecIF:Diagram)
- SpecIF:Diagram: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
- SpecIF:Notation: SysML Requirement Diagram (req)

## Transport to Target (IREB:Requirement)
- dcterms:identifier: 1
- dcterms:description: As a customer I would like to get a parcel delivered from the current location C to a target location T.
- SpecIF:Status: 40_approved
- SpecIF:Stereotype: Function Requirement (IREB)

## Navigation (IREB:Requirement)
- dcterms:identifier: 2
- dcterms:description: The Vehicle shall autonomously choose the best route from the current location C to the target location T by means of a road map and actual traffic conditions.
- SpecIF:Status: 40_approved
- SpecIF:Stereotype: Function Requirement (IREB)

## Road Driving (IREB:Requirement)
- dcterms:identifier: 3
- dcterms:description: The vehicle shall be able to follow a selected road.
- SpecIF:Status: 40_approved
- SpecIF:Stereotype: Function Requirement (IREB)

## Safe Driving (IREB:Requirement)
- dcterms:identifier: 4
- dcterms:description: The vehicle shall drive no faster than allowed and adequate for the actual road condition.
- SpecIF:Status: 40_approved
- SpecIF:Stereotype: Function Requirement (IREB)

## Location as Postal Address (IREB:Requirement)
- dcterms:identifier: 5
- dcterms:description: A location may be specified as a postal address.
- SpecIF:Status: 40_approved
- SpecIF:Stereotype: Function Requirement (IREB)

## Location as GPS Coordinate (IREB:Requirement)
- dcterms:identifier: 6
- dcterms:description: A location may be specified as GPS Coordinate with Longitude and Latitude in Degrees.
- SpecIF:Status: 40_approved
- SpecIF:Stereotype: Function Requirement (IREB)

## Obstacle Avoidance (IREB:Requirement)
- dcterms:identifier: 7
- dcterms:description: The vehicle shall not hit a person or an obstacle on the road.
- SpecIF:Status: 40_approved
- SpecIF:Stereotype: Function Requirement (IREB)

## Functional Decomposition (SpecIF:Diagram)
- SpecIF:Diagram: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
- SpecIF:Notation: SysML Block Definition Diagram (bdd)
- SpecIF:Stereotype: Original Requirement Specification

## Physical Decomposition (SpecIF:Diagram)
- SpecIF:Diagram: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
- SpecIF:Notation: SysML Block Definition Diagram (bdd)
- SpecIF:Stereotype: Original Requirement Specification

## LEGO Mindstorms Vehicle (FMC:Actor)
- SpecIF:Stereotype: Component

## Chassis (FMC:Actor)
- SpecIF:Stereotype: Component

## Body (FMC:Actor)
- SpecIF:Stereotype: Component

## Drive Left (FMC:Actor)
- SpecIF:Stereotype: Component

## Drive Right (FMC:Actor)
- SpecIF:Stereotype: Component

## Support Front (FMC:Actor)
- SpecIF:Stereotype: Component

## Support Rear (FMC:Actor)
- SpecIF:Stereotype: Component

## Controller (FMC:Actor)
- SpecIF:Stereotype: Component

## Track Sensor (FMC:Actor)
- SpecIF:Stereotype: Component

## Drive to Target (FMC:Actor)
- dcterms:description: Manoevre the vehicle from the current position to the selected target.
- SpecIF:Stereotype: Function

## Navigate (FMC:Actor)
- dcterms:description: Select a path to get from the current position to the target.
- SpecIF:Stereotype: Function

## Follow the Road (FMC:Actor)
- dcterms:description: Keep the vehicle on the selected road.
- SpecIF:Stereotype: Function

## Select an adequate Speed (FMC:Actor)
- dcterms:description: Taking into account road condition and weather, select a safe speed.
- SpecIF:Stereotype: Function

## Brake in an Emergency (FMC:Actor)
- dcterms:description: Take the vehicle to a full stop in the shortest time possible without loosing control over the trajectory.
- SpecIF:Stereotype: Function

## Set Radius (FMC:Actor)
- SpecIF:Stereotype: Function

## Set Speed (FMC:Actor)
- SpecIF:Stereotype: Function

## Calculate Accelerations (FMC:Actor)
- SpecIF:Stereotype: Function

## Set Acceleration Left (FMC:Actor)
- SpecIF:Stereotype: Function

## Set Acceleration Right (FMC:Actor)
- SpecIF:Stereotype: Function

## Apply Brake (FMC:Actor)
- SpecIF:Stereotype: Function

## SmAV System-model (SysML) (SpecIF:Hierarchy)

## Statements
- Original Requirement Specification SpecIF:shows Transport to Target
- Original Requirement Specification SpecIF:shows Navigation
- Original Requirement Specification SpecIF:shows Road Driving
- Original Requirement Specification SpecIF:shows Safe Driving
- Original Requirement Specification SpecIF:shows Location as Postal Address
- Original Requirement Specification SpecIF:shows Location as GPS Coordinate
- Original Requirement Specification SpecIF:shows Obstacle Avoidance
- Navigation IREB:refines Transport to Target
- Road Driving IREB:refines Transport to Target
- Safe Driving IREB:refines Transport to Target
- Obstacle Avoidance IREB:refines Transport to Target
- Location as Postal Address IREB:refines Transport to Target
- Location as GPS Coordinate IREB:refines Transport to Target
- Physical Decomposition SpecIF:shows LEGO Mindstorms Vehicle
- Physical Decomposition SpecIF:shows Chassis
- Physical Decomposition SpecIF:shows Body
- Physical Decomposition SpecIF:shows Drive Left
- Physical Decomposition SpecIF:shows Drive Right
- Physical Decomposition SpecIF:shows Support Front
- Physical Decomposition SpecIF:shows Support Rear
- Physical Decomposition SpecIF:shows Controller
- Physical Decomposition SpecIF:shows Track Sensor
- LEGO Mindstorms Vehicle SpecIF:contains Chassis
- LEGO Mindstorms Vehicle SpecIF:contains Body
- LEGO Mindstorms Vehicle SpecIF:contains Drive Left
- LEGO Mindstorms Vehicle SpecIF:contains Drive Right
- LEGO Mindstorms Vehicle SpecIF:contains Support Front
- LEGO Mindstorms Vehicle SpecIF:contains Support Rear
- LEGO Mindstorms Vehicle SpecIF:contains Controller
- LEGO Mindstorms Vehicle SpecIF:contains Track Sensor
- Functional Decomposition SpecIF:shows Navigation
- Functional Decomposition SpecIF:shows Road Driving
- Functional Decomposition SpecIF:shows Safe Driving
- Functional Decomposition SpecIF:shows Controller
- Functional Decomposition SpecIF:shows Drive Left
- Functional Decomposition SpecIF:shows Drive Right
- Functional Decomposition SpecIF:shows Drive to Target
- Functional Decomposition SpecIF:shows Navigate
- Functional Decomposition SpecIF:shows Follow the Road
- Functional Decomposition SpecIF:shows Select an adequate Speed
- Functional Decomposition SpecIF:shows Brake in an Emergency
- Functional Decomposition SpecIF:shows Set Radius
- Functional Decomposition SpecIF:shows Set Speed
- Functional Decomposition SpecIF:shows Calculate Accelerations
- Functional Decomposition SpecIF:shows Set Acceleration Left
- Functional Decomposition SpecIF:shows Set Acceleration Right
- Functional Decomposition SpecIF:shows Apply Brake
- Follow the Road oslc_rm:satisfies Road Driving
- Select an adequate Speed oslc_rm:satisfies Safe Driving
- Navigate oslc_rm:satisfies Navigation
- Follow the Road SysML:isAssociatedWith Set Radius
- Follow the Road SysML:isAssociatedWith Select an adequate Speed
- Select an adequate Speed SysML:isAssociatedWith Set Speed
- Set Radius SysML:isAssociatedWith Calculate Accelerations
- Set Speed SysML:isAssociatedWith Calculate Accelerations
- Brake in an Emergency SysML:isAssociatedWith Calculate Accelerations
- Brake in an Emergency SysML:isAssociatedWith Apply Brake
- Calculate Accelerations SysML:isAssociatedWith Set Acceleration Left
- Calculate Accelerations SysML:isAssociatedWith Set Acceleration Right
- Drive to Target SpecIF:contains Navigate
- Drive to Target SpecIF:contains Follow the Road
- Drive to Target SpecIF:contains Brake in an Emergency
- Calculate Accelerations SysML:isAllocatedTo Controller
- Set Acceleration Left SysML:isAllocatedTo Drive Left
- Set Acceleration Right SysML:isAllocatedTo Drive Right
- Apply Brake SysML:isAllocatedTo Drive Left
- Apply Brake SysML:isAllocatedTo Drive Right
